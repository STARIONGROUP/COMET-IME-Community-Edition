# LOFT (LOFT)

# Specification: requirement
- Short-Name: requirement
- Name: requirement
- Categories: -
- IsDeprecated: false

# Specification: requirement
- Short-Name: requirement
- Name: requirement
- Categories: -
- IsDeprecated: false

## R1: oo
- Categories: -
- Requirement Text: At vero eos et accus
  
  - amus et iusto odio dignissimos ducimus qui blanditiis praesentium volu
  
  - ptatum deleniti atqu
  e corrupti quos dolores et quas mo
  
  - lestias excepturi sint occaecati cupiditate non provident, similique sunt in culpa q
  ui officia deserunt mol
  
  - 
  
  - litia animi, id est
  
  -  laborum et dolorum fuga. Et harum quidem rerum facilis est et expedita distinctio. Nam libero tem
  
  - pore, cum soluta nobis est eligendi optio cumque
   nihil impedit quo minus
  
  -  id quod maxime placeat facere possimus, omnis voluptas assumenda est, omnis dolor repellendus.
  
  -  Temporibus autem quibusdam et aut officiis debitis aut re
  
  - 
  rum necessitatibus saepe eveniet ut et voluptates repudiandae sint et molestiae non recusanda
  
  
  
  
  
  
  
  
  - kk
  
  
  - kkk
  
  
  - ooo
  
  
  - oop
  
  
  
  
  
  
  
  
  
  
  
  
  
  
  
  
  
  
  
  
  
  
  
  
  
  
  
  
  
  
  
  
  
  
  
  
  
  
  
  
  
  
  
  
  
  
  e. Itaque earum rerum hic tenetur a sapiente delectus, ut aut reiciendis voluptatibus maiores alias cons
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  j
- IsDeprecated: false

## R2: SquareWheels
- Categories: -
- Requirement Text:
  - t
  
  
  - h
  
  - e
  
  - w
  
  - h
  
  - e
  
  - e
  
  - l
  
  - s
  
  - s
  
  - h
  
  - a
  
  - l
  
  - l
  
  - a
  
  - l
  
  - 
  
  - l
  
  - b
  
  - e
  
  - s
  
  - q
  
  - u
  
  - a
  
  - r
  
  - e
  
  -
- IsDeprecated: false

## R3: refg
- Categories: -
- 43 [-]
- Requirement Text: At vero eos et accusamus et iusto odio dignissimos ducimus qui blanditiis praesentium voluptatum deleniti atque corrupti quos dolores et quas molestias excepturi sint occaecati cupiditate non provident, similique sunt in culpa qui officia deserunt mollitia animi, id est laborum et dolorum fuga. Et harum quidem rerum facilis est et expedita distinctio. Nam libero tempore, cum soluta nobis est eligendi optio cumque nihil impedit quo minus id quod maxime placeat facere possimus, omnis voluptas assumenda est, omnis dolor repellendus. Temporibus autem quibusdam et aut officiis debitis aut rerum necessitatibus saepe eveniet ut et voluptates repudiandae sint et molestiae non recusandae. Itaque earum rerum hic tenetur a sapiente delectus, ut aut reiciendis voluptatibus maiores alias cons
- IsDeprecated: false
