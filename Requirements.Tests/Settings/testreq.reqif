# LOFT (LOFT)

# Specification: requirement
- Short-Name: requirement
- Name: requirement
- Categories: -
- IsDeprecated: true

# Specification: SPEC_0002
- Short-Name: SPEC_0002
- Name: requirement
- Categories: -
- IsDeprecated: true

## R1: -
- Short-Name: oo
- IsDeprecated: false

## R2: refg
- Short-Name: REQ_0003
- Categories: -
- IsDeprecated: false

## R3: SquareWheels
- Short-Name: REQ_0002
- Categories: -
- IsDeprecated: false

# Specification: SPEC_0001
- Short-Name: SPEC_0001
- Name: requirement
- Categories: -
- IsDeprecated: true

# Specification: requirement
- Short-Name: requirement
- Name: requirement
- Categories: -
- IsDeprecated: true

# Specification: requirement
- Short-Name: requirement
- Name: requirement
- Categories: -
- IsDeprecated: true

# Specification: requirement
- Short-Name: requirement
- Name: requirement
- Categories: -
- IsDeprecated: true

## R4: refg
- Categories: -
- IsDeprecated: false

## R5: SquareWheels
- Categories: -
- IsDeprecated: false

## R6: oo
- Categories: -
- IsDeprecated: false

# Specification: requirement
- Short-Name: requirement
- Name: requirement
- Categories: -
- IsDeprecated: true

## R7: oo
- Short-Name: REQ_0001
- Categories: -
- IsDeprecated: false

## R8: refg
- Short-Name: REQ_0003
- Categories: -
- IsDeprecated: false

## R9: SquareWheels
- Short-Name: REQ_0002
- Categories: -
- IsDeprecated: false

# Specification: requirement
- Short-Name: requirement
- Name: requirement
- Categories: -
- IsDeprecated: true

## R10: oo
- Categories: -
- Requirement Text: At vero eos et accus
  
  - amus et iusto odio dignissimos ducimus qui blanditiis praesentium volu
  
  - ptatum deleniti atqu
  e corrupti quos dolores et quas mo
  
  - lestias excepturi sint occaecati cupiditate non provident, similique sunt in culpa q
  ui officia deserunt mol
  
  - 
  
  - litia animi, id est
  
  -  laborum et dolorum fuga. Et harum quidem rerum facilis est et expedita distinctio. Nam libero tem
  
  - pore, cum soluta nobis est eligendi optio cumque
   nihil impedit quo minus
  
  -  id quod maxime placeat facere possimus, omnis voluptas assumenda est, omnis dolor repellendus.
  
  -  Temporibus autem quibusdam et aut officiis debitis aut re
  
  - 
  rum necessitatibus saepe eveniet ut et voluptates repudiandae sint et molestiae non recusanda
  
  
  
  
  
  
  
  
  - kk
  
  
  - kkk
  
  
  - ooo
  
  
  - oop
  
  
  
  
  
  
  
  
  
  
  
  
  
  
  
  
  
  
  
  
  
  
  
  
  
  
  
  
  
  
  
  
  
  
  
  
  
  
  
  
  
  
  
  
  
  
  e. Itaque earum rerum hic tenetur a sapiente delectus, ut aut reiciendis voluptatibus maiores alias cons
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  j
- IsDeprecated: false

## R11: SquareWheels
- Categories: -
- Requirement Text:
  - t
  
  
  - h
  
  - e
  
  - w
  
  - h
  
  - e
  
  - e
  
  - l
  
  - s
  
  - s
  
  - h
  
  - a
  
  - l
  
  - l
  
  - a
  
  - l
  
  - 
  
  - l
  
  - b
  
  - e
  
  - s
  
  - q
  
  - u
  
  - a
  
  - r
  
  - e
  
  -
- IsDeprecated: false

## R12: refg
- Categories: -
- 43 [-]
- Requirement Text: At vero eos et accusamus et iusto odio dignissimos ducimus qui blanditiis praesentium voluptatum deleniti atque corrupti quos dolores et quas molestias excepturi sint occaecati cupiditate non provident, similique sunt in culpa qui officia deserunt mollitia animi, id est laborum et dolorum fuga. Et harum quidem rerum facilis est et expedita distinctio. Nam libero tempore, cum soluta nobis est eligendi optio cumque nihil impedit quo minus id quod maxime placeat facere possimus, omnis voluptas assumenda est, omnis dolor repellendus. Temporibus autem quibusdam et aut officiis debitis aut rerum necessitatibus saepe eveniet ut et voluptates repudiandae sint et molestiae non recusandae. Itaque earum rerum hic tenetur a sapiente delectus, ut aut reiciendis voluptatibus maiores alias cons
- IsDeprecated: false

# Specification: requirement
- Short-Name: requirement
- Name: requirement
- Categories: CategoryRequirement
- IsDeprecated: true

# Specification: requirement
- Short-Name: requirement
- Name: requirement
- Categories: -
- IsDeprecated: true

# Specification: requirement
- Short-Name: requirement
- Name: requirement
- Categories: CategoryRequirement
- IsDeprecated: false

## R13: refg
- Categories: -
- IsDeprecated: false

## R14: oo
- Categories: -
- IsDeprecated: false

## R15: SquareWheels
- Categories: -
- IsDeprecated: false
- BinaryRelationship -> R6

# Specification: requirement
- Short-Name: requirement
- Name: requirement
- Categories: -
- IsDeprecated: true

## R16: oo
- Categories: -
- Requirement Text: At vero eos et accus
  
  - amus et iusto odio dignissimos ducimus qui blanditiis praesentium volu
  
  - ptatum deleniti atqu
  e corrupti quos dolores et quas mo
  
  - lestias excepturi sint occaecati cupiditate non provident, similique sunt in culpa q
  ui officia deserunt mol
  
  - 
  
  - litia animi, id est
  
  -  laborum et dolorum fuga. Et harum quidem rerum facilis est et expedita distinctio. Nam libero tem
  
  - pore, cum soluta nobis est eligendi optio cumque
   nihil impedit quo minus
  
  -  id quod maxime placeat facere possimus, omnis voluptas assumenda est, omnis dolor repellendus.
  
  -  Temporibus autem quibusdam et aut officiis debitis aut re
  
  - 
  rum necessitatibus saepe eveniet ut et voluptates repudiandae sint et molestiae non recusanda
  
  
  
  
  
  
  
  
  - kk
  
  
  - kkk
  
  
  - ooo
  
  
  - oop
  
  
  
  
  
  
  
  
  
  
  
  
  
  
  
  
  
  
  
  
  
  
  
  
  
  
  
  
  
  
  
  
  
  
  
  
  
  
  
  
  
  
  
  
  
  
  e. Itaque earum rerum hic tenetur a sapiente delectus, ut aut reiciendis voluptatibus maiores alias cons
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  
  j
- IsDeprecated: false

## R17: SquareWheels
- Categories: -
- Requirement Text:
  - t
  
  
  - h
  
  - e
  
  - w
  
  - h
  
  - e
  
  - e
  
  - l
  
  - s
  
  - s
  
  - h
  
  - a
  
  - l
  
  - l
  
  - a
  
  - l
  
  - 
  
  - l
  
  - b
  
  - e
  
  - s
  
  - q
  
  - u
  
  - a
  
  - r
  
  - e
  
  -
- IsDeprecated: false

## R18: refg
- Categories: -
- Requirement Text: At vero eos et accusamus et iusto odio dignissimos ducimus qui blanditiis praesentium voluptatum deleniti atque corrupti quos dolores et quas molestias excepturi sint occaecati cupiditate non provident, similique sunt in culpa qui officia deserunt mollitia animi, id est laborum et dolorum fuga. Et harum quidem rerum facilis est et expedita distinctio. Nam libero tempore, cum soluta nobis est eligendi optio cumque nihil impedit quo minus id quod maxime placeat facere possimus, omnis voluptas assumenda est, omnis dolor repellendus. Temporibus autem quibusdam et aut officiis debitis aut rerum necessitatibus saepe eveniet ut et voluptates repudiandae sint et molestiae non recusandae. Itaque earum rerum hic tenetur a sapiente delectus, ut aut reiciendis voluptatibus maiores alias cons
- IsDeprecated: false
